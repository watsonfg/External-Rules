'Rule to get values from part and return to assembly
'External rule for easier global maintenance of ALL Wood Assemblies

'['External Debug Routine
AddVbFile "DebugHelper.vb" 'Defines external rule
Dim Dbg as New DebugHelper(ThisDoc.Document,SharedVariable)
'Dbg.Log("Executing WoodAsm")
'Dbg.DumpProperties()
']

'['Get driving models preference for showing "OK" testing messages via SharedVariable
If Not SharedVariable.Exists("ShowOkMsgWoodAsm") Then 'force false
	'MessageBox.Show("Shared Variable does NOT Exist!", "Please send 'ShowOkMsgWoodAsm' to WoodAsm")
	ShowOkMsgWoodAsm = False
	'MessageBox.Show("Message Boxes will show for WoodAsm values", "ShowOkMsgWoodAsm value set to 'True' ")
Else'set to user preference
	ShowOkMsgWoodAsm = SharedVariable("ShowOkMsgWoodAsm")
	'MessageBox.Show("ShowOkMsgWoodAsm value: " & ShowOkMsgWoodAsm, "ShowOkMsgWoodAsm value")
End If
']

'['Toggles to control message boxes, and get FileName
'Toggles all Error message boxes in parts running this rule.
'Uses Environment Variable from Computer running Inventor
'Set to "true" for development PC and "false" for Server running Frontier cadflow.
'(Ensures Auto Off when model Is published)
Dim ErrMsg As String = Environ("ILOGIC_ErrMsg")
If ErrMsg = "true" Then 
ShowErrMsg = True
Else		'If the PC is missing the Enviornment Variable then ShowErrWarnMsg will be set to false 
ShowErrMsg = False
	If ShowOkMsgWoodAsm = True Then
		ShowOkMsgWoodAsm = False	'Safety rule, override true back to false in case on server
	End If
End If

PartName = ThisDoc.FileName(True) 'with extension
']

'['Verify incoming arguments then get values
app = ThisApplication
If (Not RuleArguments.Exists("SendPartName")) Then
Dbg.Log("Above called External: WoodAsm, Argument SendPartName was not provided")
If ShowErrMsg Then MessageBox.Show("No Incoming Argument", "SendPartName")
Else
SentPartName = RuleArguments("SendPartName")
'OFF for now, is in other msgboxes If ShowOkMsgWoodAsm Then MessageBox.Show("  Sent Part Name =    " & SentPartName, "Working within " & PartName)	
'Dbg.Log("Executing WoodAsm, SentPartName Value= " & SentPartName)

'scheme to assign values from part to assembly and check for errors about missing iProperties
	On Error Resume Next
	
		iProperties.Value("Custom", "SQFT") = iProperties.Value(SentPartName, "Custom", "SQFT")
		If Err.Number <> 0 Then
			_errorState = True
			_strErrorValue = _strErrorValue & "\\nNo SQFT iProperty Defined for this Part or Asm"
			Err.clear
		End If
		If ShowOkMsgWoodAsm Then MessageBox.Show("Part:  " & SentPartName & "   ,   SQFT: " & iProperties.Value("Custom", "SQFT"), "ShowOkMsgWoodAsm In external rule:")
		
		iProperties.Value("Custom", "EDGSEQ") = iProperties.Value(SentPartName, "Custom", "EDGSEQ")
		If Err.Number <> 0 Then
			_errorState = True
			_strErrorValue = _strErrorValue & "\\nNo EDGSEQ iProperty Defined for this Part or Asm"
			Err.clear
		End If
		If ShowOkMsgWoodAsm Then MessageBox.Show("Part:  " & SentPartName & "   ,   EDGSEQ: " & iProperties.Value("Custom", "EDGSEQ"), "ShowOkMsgWoodAsm In external rule:")
'conditional check here for EDGLFT only
		If Not iProperties.Value("Custom", "EDGSEQ") = "NONE" Then 'only try to get EdgLft based on EDGSEQ, GH removed "NO EDGE" on 11/4/14, only want "NONE"
			iProperties.Value(SentPartName, "Custom", "EDGLFT")=Ceil(iProperties.Value(SentPartName, "Custom", "EDGLFT"))
			iProperties.Value("Custom", "EDGLFT") = iProperties.Value(SentPartName, "Custom", "EDGLFT")
			If Err.Number <> 0 Then
				_errorState = True
				_strErrorValue = _strErrorValue & "\\nNo EDGLFT iProperty Defined for this Part or Asm"
				Err.clear
			End If
		End If
		If ShowOkMsgWoodAsm Then MessageBox.Show("Part:  " & SentPartName & "   ,   EDGLFT: " & iProperties.Value("Custom", "EDGLFT"), "ShowOkMsgWoodAsm In external rule:")


		iProperties.Value("Custom", "ERRORS") = iProperties.Value(SentPartName, "Custom", "ERRORS")
		If Err.Number <> 0 Then
			_errorState = True
			_strErrorValue = _strErrorValue & "\\nNo ERRORS iProperty Defined for this Part or Asm"
		Err.clear
		End If	
		If ShowOkMsgWoodAsm Then MessageBox.Show("Part:  " & SentPartName & "   ,   ERRORS: " & iProperties.Value("Custom", "ERRORS"), "ShowOkMsgWoodAsm In external rule:")


		iProperties.Value("Custom", "WARNINGS") = iProperties.Value(SentPartName, "Custom", "WARNINGS")
		If Err.Number <> 0 Then
			_errorState = True
			_strErrorValue = _strErrorValue & "\\nNo WARNINGS iProperty Defined for this Part or Asm"
			Err.clear
		End If	
		If ShowOkMsgWoodAsm Then MessageBox.Show("Part:  " & SentPartName & "   ,   WARNINGS: " & iProperties.Value("Custom", "WARNINGS"), "ShowOkMsgWoodAsm In external rule:")


		iProperties.Value("Custom", "RLOAD") = iProperties.Value(SentPartName, "Custom", "RLOAD")
		If Err.Number <> 0 Then
			_errorState = True
			_strErrorValue = _strErrorValue & "\\nNo RLOAD iProperty Defined for this Part or Asm"
			Err.clear
		End If	
		If ShowOkMsgWoodAsm Then MessageBox.Show("Part:  " & SentPartName & "   ,   RLOAD: " & iProperties.Value("Custom", "RLOAD"), "ShowOkMsgWoodAsm In external rule:")


		iProperties.Value("Custom", "CUTA") = iProperties.Value(SentPartName, "Custom", "CUTA")
		If Err.Number <> 0 Then
			_errorState = True
			_strErrorValue = _strErrorValue & "\\nNo CUTA iProperty Defined for this Part or Asm"
			Err.clear
		End If	
		If ShowOkMsgWoodAsm Then MessageBox.Show("Part:  " & SentPartName & "   ,   CUTA: " & iProperties.Value("Custom", "CUTA"), "ShowOkMsgWoodAsm In external rule:")

		iProperties.Value("Custom", "CUTB") = iProperties.Value(SentPartName, "Custom", "CUTB")
		If Err.Number <> 0 Then
			_errorState = True
			_strErrorValue = _strErrorValue & "\\nNo CUTB iProperty Defined for this Part or Asm"
			Err.clear
		End If	
		If ShowOkMsgWoodAsm Then MessageBox.Show("Part:  " & SentPartName & "   ,   CUTB: " & iProperties.Value("Custom", "CUTB"), "ShowOkMsgWoodAsm In external rule:")

	'conditional check here for CUTEDG1 thru 5
	'only try to get CUTEDG# based on ipt value, don't want error msg or auto add iProperty
		If iProperties.Value(SentPartName, "Custom", "CUTEDG1") >= 0 Then iProperties.Value("Custom", "CUTEDG1") = iProperties.Value(SentPartName, "Custom", "CUTEDG1")
		If iProperties.Value(SentPartName, "Custom", "CUTEDG2") >= 0 Then iProperties.Value("Custom", "CUTEDG2") = iProperties.Value(SentPartName, "Custom", "CUTEDG2")
		If iProperties.Value(SentPartName, "Custom", "CUTEDG3") >= 0 Then iProperties.Value("Custom", "CUTEDG3") = iProperties.Value(SentPartName, "Custom", "CUTEDG3")
		If iProperties.Value(SentPartName, "Custom", "CUTEDG4") >= 0 Then iProperties.Value("Custom", "CUTEDG4") = iProperties.Value(SentPartName, "Custom", "CUTEDG4")
		If iProperties.Value(SentPartName, "Custom", "CUTEDG5") >= 0 Then iProperties.Value("Custom", "CUTEDG5") = iProperties.Value(SentPartName, "Custom", "CUTEDG5")
'		
'['''GH added 8/29/12, as of 1/9/13 change ManualUpdate to true to conditionally check and change each part number. 
	'AutoUpdate Is Not tested, keep it False. Also added ruff code to check and change ErpOp
''''************************************************************************************************************
''''************************************************************************************************************
ManualUpdate = False'''***just change this to true or false
AutoUpdate = False

If ManualUpdate Or AutoUpdate Then
	OriginalPartNumber = iProperties.Value(SentPartName, "Project", "Part Number")
	''Best To keep this next line Off, PN Is built into Main message...
	''MessageBox.Show(OriginalPartNumber, "ist Temp Test of OriginalPartNumber")
	If OriginalPartNumber Like "STR*" Then
		If ShowErrMsg Then
			''Conditional Or Automatic
			MsgTxt = "Do you want to add 'T' Prefix to this Original Part Number? : " & OriginalPartNumber & "  "
			i = MessageBox.Show(MsgTxt, "Add 'T' Prefix.", MessageBoxButtons.YesNo, MessageBoxIcon.None, MessageBoxDefaultButton.Button1)
			''from testing Y=6, N=7
			If i = 6 Then iProperties.Value(SentPartName, "Project", "Part Number") = "T" & OriginalPartNumber
		End If
			''Automatic, keep this next line off unless its time for a global change
			If AutoUpdate Then iProperties.Value(SentPartName, "Project", "Part Number") = "T" & OriginalPartNumber
	ElseIf OriginalPartNumber Like "SPPRT-PANEL-CP*" Then
		If ShowErrMsg Then
			MsgTxt = "Must Stop! We can't auto add 'T' Prefix because this Original Part Number : " & OriginalPartNumber & " is not a regular PN begining with STR... "
			MessageBox.Show(MsgTxt, "Must stop trying to Add 'T' Prefix.")
			ERRORS = ERRORS & "Must Stop! We can't auto add 'T' Prefix because this Original Part Number : " & OriginalPartNumber & " is not a regular PN begining with STR... "
		End If
	End If
	
	OriginalErpOp = iProperties.Value(SentPartName, "Custom", "ERP_OPERATION")
	EDGSEQ = iProperties.Value(SentPartName, "Custom", "EDGSEQ")
	POCKET = iProperties.Value(SentPartName, "Custom", "POCKET")
	If OriginalErpOp Like "4##" Then
		If EDGSEQ Like "[12][AB]*" Then
			MsgTxt = "Do you want to change ErpOp from '" & OriginalErpOp & "' to 500 for the Part Number? : " & OriginalPartNumber & " With EDGSEQ of: " & EDGSEQ & "  "
			i = MessageBox.Show(MsgTxt, "Add 'T' Prefix.", MessageBoxButtons.YesNo, MessageBoxIcon.None, MessageBoxDefaultButton.Button1)
			''from testing Y=6, N=7
			If i = 6 Then iProperties.Value(SentPartName, "Custom", "ERP_OPERATION") = 500
		Else
			'looking for no edge
			If Not OriginalErpOp = 460 Then
				MsgTxt = "Do you want to change ErpOp from '" & OriginalErpOp & "' to 460 for the Part Number? : " & OriginalPartNumber & " With EDGSEQ of: " & EDGSEQ & "  and with POCKET of: " & POCKET & "  "
				i = MessageBox.Show(MsgTxt, "Add 'T' Prefix.", MessageBoxButtons.YesNo, MessageBoxIcon.None, MessageBoxDefaultButton.Button1)
				''from testing Y=6, N=7
				If i = 6 Then iProperties.Value(SentPartName, "Custom", "ERP_OPERATION") = 460
			End If
		End If
	End If 
End If
']' block ends here

	On Error Goto 0
		If _errorState = True Then
		If ShowErrMsg Then MessageBox.Show("Part: " & SentPartName & " , " & _strErrorValue, "Error In external WoodAsm rule:")
		End If	
End If
 ']
 
 iLogicVb.RunExternalRule("EnsureLod")
 
 
 
 '['GH added some quick automated safety checks 1/3/13 to catch simple common issues
 
 'combine and capture any previous errors from above routines
 ERRORS = ERRORS & iProperties.Value("Custom", "ERRORS")
 
 If Not iProperties.Value(SentPartName, "Project", "Stock Number") = "" Then
 	ERRORS = ERRORS & "There is a value in the 'Stock Number' field of: '" & iProperties.Value(SentPartName, "Project", "Stock Number") & "'  which must be removed. We only use 'Part Number'!       "
End If
 
 'compare iam to ipt Part Number... should never match, may catch simple failure to check if Inventor overwrote the Part Number on save 
If iProperties.Value("Project", "Part Number") = iProperties.Value(SentPartName, "Project", "Part Number") Then
	If Not iProperties.Value("Project", "Part Number") = "COUNTERWEIGHT" Then
		ERRORS = ERRORS & "The iam and ipt both have the same 'Part Number' of: '" & iProperties.Value(SentPartName, "Project", "Part Number") & "' which cannot be correct!    "
	End If
End If


''' *** only due in development, don't want to stop OE for these issues ***
If ShowErrMsg Then
	'GH Added 1/9/13 to enforce consistent term without space to resolve PCM issues
	EDGSEQ = iProperties.Value("Custom", "EDGSEQ")
	ERP_OPERATION = iProperties.Value(SentPartName,"Custom", "ERP_OPERATION")
	If EDGSEQ = "NO EDGE" Then
		ERRORS = ERRORS & "Must change EDGSEQ term from 'NO EDGE' to 'NONE'! Auto fixed to 'NONE' but must check in rules too. Part Number: '" & iProperties.Value(SentPartName, "Project", "Part Number") & "   "
		iProperties.Value(SentPartName,"Custom", "EDGSEQ") = "NONE"
	End If
	
	If EDGSEQ = "NONE" And (ERP_OPERATION >= 500 And ERP_OPERATION <= 511) Then
		ERRORS = ERRORS & "Must check ERP_OPERATION of '" & ERP_OPERATION & "' for part with EDGSEQ of 'NONE'!  Part Number: '" & iProperties.Value(SentPartName, "Project", "Part Number") & "   "
	End If
	
	
	'''Check if POCKET iProperty exists at ipt
	'GH added next chunk of code because ipt had POCKET with bad values but no POCKET existed on iam. 7/25/13
	On Error Resume Next
	'MessageBox.Show("Message Pre Test for missing POCKET, ErrNumber=" & Err.Number, "Title")
	POCKET = iProperties.Value(SentPartName,"Custom", "POCKET")
	If Err.Number <> 0 Then
		'don't set an _errorState, just skip checking the POCKET value... and clear the err
		'MessageBox.Show("Message For Testing a missing POCKET, ErrNumber=" & Err.Number, "Title")
		Err.clear
	Else' err must be zero, so check the value
		'MessageBox.Show("Message For Existing POCKET: " & POCKET, "Title")
		If Not (POCKET Like "[AB]" Or POCKET = "NA" Or POCKET = "") Then
			ERRORS = ERRORS & "POCKET term must be 'A', 'B', or 'NA' or blank,  Not '" & POCKET & "'    Part Number: '" & iProperties.Value(SentPartName, "Project", "Part Number") & "  "
		Else
		'update the iam  with the ipt value
		iProperties.Value("Custom", "POCKET") = POCKET
		'could check that 'B' are going to ErpOp 460
		End If
	End If	
	
		On Error Goto 0
		If _errorState = True Then
		If ShowErrMsg Then MessageBox.Show("Part: " & SentPartName & " , " & _strErrorValue, "Error In external WoodAsm rule:")
		End If		
	
	
	'''Check if POCKET iProperty exists at iam
	On Error Resume Next
	'MessageBox.Show("Message Pre Test for missing POCKET, ErrNumber=" & Err.Number, "Title")
	POCKET = iProperties.Value("Custom", "POCKET")
	If Err.Number <> 0 Then
		'don't set an _errorState, just skip checking the POCKET value... and clear the err
		'MessageBox.Show("Message For Testing a missing POCKET, ErrNumber=" & Err.Number, "Title")
		Err.clear
	Else' err must be zero, so check the value
		'MessageBox.Show("Message For Existing POCKET: " & POCKET, "Title")
		If Not (POCKET Like "[AB]" Or POCKET = "NA" Or POCKET = "") Then
			ERRORS = ERRORS & "POCKET term must be 'A', 'B', or 'NA' or blank,  Not '" & POCKET & "'    Part Number: '" & iProperties.Value(SentPartName, "Project", "Part Number") & "  "
		Else
		'could check that 'B' are going to ErpOp 460
		End If
	End If	
	
		On Error Goto 0
		If _errorState = True Then
		If ShowErrMsg Then MessageBox.Show("Part: " & SentPartName & " , " & _strErrorValue, "Error In external WoodAsm rule:")
		End If	
		
End If
 ']
 
 '['Save this untill PREMILL gets resolved
 '''Developed 1st on 4/3/14 expecting ipt to be published with PREMILL, replaced by below.
 
' '['GH added 4/3/14 for automated way to get PREMILL iProperty from ipt to iam
' '''can be removed after all are populated
'
''''Check if PREMILL iProperty exists at ipt
'On Error Resume Next
''MessageBox.Show("Message Pre Test for missing PREMILL, ErrNumber=" & Err.Number, "Title")
'PREMILL = iProperties.Value(SentPartName,"Custom", "PREMILL")
'If Err.Number <> 0 Then
'	'don't set an _errorState, just skip checking the PREMILL value... and clear the err
'	'MessageBox.Show("Message For Testing a missing PREMILL, ErrNumber=" & Err.Number, "Title")
'	Err.clear
'Else' err must be zero, so check the value and add it to iam
'	'MessageBox.Show("Message For Existing PREMILL: " & PREMILL, "Title")
'	If PREMILL = "" Then
'		ERRORS = ERRORS & "PREMILL must have a value.    Part Number: '" & iProperties.Value(SentPartName, "Project", "Part Number") & "  "
'	Else
'	'update the iam  with the ipt value
'	iProperties.Value("Custom", "PREMILL") = PREMILL
'	End If
'End If	
'
'	On Error Goto 0
'	If _errorState = True Then
'	If ShowErrMsg Then MessageBox.Show("Part: " & SentPartName & " , " & _strErrorValue, "Error In external WoodAsm rule:")
'	End If		
' ']
']

'['GH added 4/3/14 for automated way to create PREMILL iProperty in ipt and then iam, all based on specific details in ipt
'''tweaked on 11/4/14 added 0.040 value and want 'NOPREMIL' for EDGSEQ of NONE or C
'''can be removed after all are populated... ??
'''See if its a *STR* part, with EDGSEQ, not like C...
On Error Resume Next
PartNum = iProperties.Value(SentPartName, "Project", "Part Number")
If PartNum Like "TSTR*" Or PartNum = "ENDPNL-CP" Or PartNum = "EDSK-PAN-CP" Or PartNum = "TDSK-PAN-CP" Or PartNum = "TC-PANEL-CP" Or PartNum = "TSCRN-CP" Or PartNum = "TSTVD-CP" Or PartNum = "S12-1104DPS-CP" Or PartNum = "S12-1104DEP-CP" Or PartNum = "S13-0500-DP-CP" Or PartNum = "TSTVDV-CP" Or PartNum = "TSTLSD-CP" Then
	'''Get all needed values, then Validate, then Update or return Error
	
	'Get EDGSEQ value, this had no confirmation before
	EDGSEQ = iProperties.Value(SentPartName, "Custom", "EDGSEQ")
	EDGTHK = iProperties.Value(SentPartName, "Custom", "EDGTHK")
		If Err.Number <> 0 Then
			Err.clear
			CheckParameterEDGTHK = Parameter(SentPartName, "EDGTHK")
			If Err.Number <> 0 Then 
				ERRORS = ERRORS  & "\\nNo EDGTHK iProperty Defined for this Part or Asm and no EDGTHK Parameter."  & " From file named: " & PartName
			Else
				'found EDGTHK parameter, create the missing iProperty and set the EDGTHK value
				iProperties.Value(SentPartName, "Custom", "EDGTHK") = Parameter(SentPartName, "EDGTHK")
				EDGTHK = Parameter(SentPartName, "EDGTHK")
			End If			
		End If
	
	'Check if PREMILL iProperty exists at ipt
	'MessageBox.Show("Message Pre Test for missing PREMILL, ErrNumber=" & Err.Number, "Title")
	PREMILL = iProperties.Value(SentPartName, "Custom", "PREMILL")
		If Err.Number <> 0 Then
			'No PREMILL on ipt, don't set an _errorState, clear the err, create the iProperty with default string as needed in both ipt and iam
			iProperties.Value(SentPartName, "Custom", "PREMILL") = "JustCreatedThisMissingIproperty"
			iProperties.Value("Custom", "PREMILL") = "JustCreatedThisMissingIproperty"
			PREMILL = iProperties.Value(SentPartName, "Custom", "PREMILL")
			'MessageBox.Show("Message For Testing a missing PREMILL, need to create, ErrNumber=" & Err.Number, "Title")
			Err.clear
			
			
			
			
			
		Else'has PREMILL on ipt so check the value and add it to iam if needed
			'MessageBox.Show("Message For Existing PREMILL: " & PREMILL, "Title")
			If Not (PREMILL = "0.059" Or PREMILL = "0.030" Or PREMILL = "0.040" Or PREMILL = "NOPREMIL") Then
				ERRORS = ERRORS & "PREMILL must be '0.059' or '0.030' or '0.040' or 'NOPREMIL' ,  Not '" & PREMILL & "'    Part Number: '" & iProperties.Value(SentPartName, "Project", "Part Number") & "  "
			Else
				'Values OK so update the iam  with the ipt value
				PREMILL = iProperties.Value("Custom", "PREMILL")
				If Err.Number <> 0 Then
					'No PREMILL on iam, don't set an _errorState, clear the err, create the value in only iam
					iProperties.Value("Custom", "PREMILL") = CStr(EDGTHK)
					'MessageBox.Show("Message For Testing a missing PREMILL, need to create, ErrNumber=" & Err.Number, "Title")
					Err.clear
				Else
					'has PREMILL on both iam and ipt so should be OK
					'temp convert value to text
					If IsNumeric(PREMILL) Then
						iProperties.Value("Custom", "PREMILL") = CStr(EDGTHK)
					End If
				End If
			End If
		End If
	
	
	
		
	
	
	If Not (EDGSEQ = "NONE" Or EDGSEQ = "C") Then
		'Want add PREMILL, get EDGTHK Value
		EDGTHK = iProperties.Value(SentPartName, "Custom", "EDGTHK")
		If Err.Number <> 0 Then
			Err.clear
			CheckParameterEDGTHK = Parameter(SentPartName, "EDGTHK")
			If Err.Number <> 0 Then 
				ERRORS = ERRORS  & "\\nNo EDGTHK iProperty Defined for this Part or Asm and no EDGTHK Parameter."  & " From file named: " & PartName
			Else
				'found EDGTHK parameter, create the missing iProperty and set the EDGTHK value
				iProperties.Value(SentPartName, "Custom", "EDGTHK") = Parameter(SentPartName, "EDGTHK")
				EDGTHK = Parameter(SentPartName, "EDGTHK")
			End If			
		End If
		If EDGTHK = "0.059" Or EDGTHK = "0.030" Or EDGTHK = "0.040" Then
			'Check if PREMILL iProperty exists at ipt
			'MessageBox.Show("Message Pre Test for missing PREMILL, ErrNumber=" & Err.Number, "Title")
			PREMILL = iProperties.Value(SentPartName, "Custom", "PREMILL")
			If Err.Number <> 0 Then
				'No PREMILL on ipt, don't set an _errorState, clear the err, create the value in both ipt and iam
				iProperties.Value(SentPartName, "Custom", "PREMILL") = CStr(EDGTHK)
				iProperties.Value("Custom", "PREMILL") = CStr(EDGTHK)
				'MessageBox.Show("Message For Testing a missing PREMILL, need to create, ErrNumber=" & Err.Number, "Title")
				Err.clear
			Else'has PREMILL on ipt so check the value and add it to iam if needed
				'MessageBox.Show("Message For Existing PREMILL: " & PREMILL, "Title")
				If Not (PREMILL = "0.059" Or PREMILL = "0.030" Or PREMILL = "0.040" Or PREMILL = "NOPREMIL") Then
					ERRORS = ERRORS & "PREMILL must be '0.059' or '0.030' or '0.040' ,  Not '" & PREMILL & "'    Part Number: '" & iProperties.Value(SentPartName, "Project", "Part Number") & "  "
				Else
					'Values OK so update the iam  with the ipt value
					PREMILL = iProperties.Value("Custom", "PREMILL")
					If Err.Number <> 0 Then
						'No PREMILL on iam, don't set an _errorState, clear the err, create the value in only iam
						iProperties.Value("Custom", "PREMILL") = CStr(EDGTHK)
						'MessageBox.Show("Message For Testing a missing PREMILL, need to create, ErrNumber=" & Err.Number, "Title")
						Err.clear
					Else
						'has PREMILL on both iam and ipt so should be OK
						'temp convert value to text
						If IsNumeric(PREMILL) Then
							iProperties.Value("Custom", "PREMILL") = CStr(EDGTHK)
						End If
					End If
				End If
			End If
			
		End If'Check EDGTHK
	Else' must be (EDGSEQ = "NONE" Or EDGSEQ = "C"), set PREMILL to 'NOPREMIL'
	
	
	
	
	End If'Check EDGSEQ
End If'Like TSTR*
  ']
  
iProperties.Value("Custom", "ERRORS") = ERRORS
