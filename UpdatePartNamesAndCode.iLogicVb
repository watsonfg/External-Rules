' <FireOthersImmediately>False</FireOthersImmediately>

Sub Main()
	'Try to open document as assembly type
	Dim oDoc As AssemblyDocument = ThisDoc.Document
	replaceText = GenerateTextFile("ReplaceText")
	
	'confirm that the text to be changed is recorded properly
	confirmChange = MessageBox.Show("Have you saved out the files already as the updated names?", "Confirm Choice",MessageBoxButtons.YesNo, MessageBoxIcon.Question)
	If confirmChange = vbNo
		Exit Sub
	End If

	'Determine what should be replaced
	oldText = InputBox("What string of the part name would you like to replace (MUST BE START OF PARTNAME)", "Text to Remove", "", MessageBoxIcon.Information)
	newText = InputBox("What would you like to replace it with?", "Text to Add", "", MessageBoxIcon.Information)
	
	'confirm that the text to be changed is recorded properly
	confirmChange = MessageBox.Show("Are you SURE you want to replace " & oldText & " with " & newText, "Confirm Choice",MessageBoxButtons.YesNo, MessageBoxIcon.Question)
	If confirmChange = vbNo
		Exit Sub
	End If
	
	'Replace New Parts
	ReplacePartsLog = ReplacePartsAsm(oDoc, oldText, newText)

	'Update Part names
	PartNameUpdateLog = UpdatePartNamesAsm(oDoc, oldText, newText)

	'Update file names in code
	CodeUpdateLog = UpdateCodeAsm(oDoc, oldText, newText)
	
	'Write out to text file
	WriteText(replaceText, ReplacePartsLog)
	WriteText(replaceText, PartNameUpdateLog)
	WriteText(replaceText, CodeUpdateLog)

	openTextFile(replaceText)
End Sub


Public Function ReplacePartsAsm(oDoc As AssemblyDocument, oldText As String, newText As String) As String
	'''Creator: Chris Kuchman
	'''Date Made: 6/17/2020
	'''Date Updated: 
	'''Description: Takes in a assembly document and checks all subordinate parts to see if there is a file present in the same folder as
	'''the top level assembly that contains a file name that matches the replaced front of the string.
	'''Example: A case where oldText=BAD and newText=GOOD. A subordinate part called BADPART.iam is checked to see if a GOODPART.iam lives
	'''in the same folder as the passed in assembly. If so, the part is replaced and then this is process is reran with GOODPART.iam as the 
	'''assembly (checking all their children). If the files were named PARTBAD.iam and PARTGOOD.iam, no change would occur and the assembly would be skipped.
	'''Returns: A string log of the successful and failed updates
	
	'Generate text blocks for the final results
	ReplacedText = ""
	IgnoredNoFileText = ""
	SubOutputText = ""
	
	'Determine the documents path
	pathLength = InStrRev(oDoc.FullFileName, "\", -1)
	oDocPath = Left(oDoc.FullFileName, PathLength)
	
	'Check each occurence in specified document
	For Each occ As ComponentOccurrence In oDoc.ComponentDefinition.Occurrences

			'Check to see if the alternative part is present
			'Get file name with extension
			refDoc = GetDocumentFromOccurence(occ)
			fileName = GetFileNameNoPathForDoc(refDoc, True)

			'Generate possible new part name
			newName = ReplaceFrontText(fileName, oldText, newText)
			
			'Check if new string was built successfully
			If Not newName = "" Then

				'Check if partname exists at level
				Try
					occ.Replace(oDocPath & newName, False)
					ReplacedText = ReplacedText & newName & vbCrLf
					
					'If the part is a assembly then recursively call this function
					If occ.DefinitionDocumentType = DocumentTypeEnum.kAssemblyDocumentObject Then
						SubOutputText = ReplacePartsAsm(GetDocumentFromOccurence(occ), oldText, newText)
					End If
				Catch
					IgnoredNoFileText = IgnoredNoFileText & newName & vbCrLf
				End Try
			End If
	Next
	
	'Generate output string log
	OutputText = OutputText & "------Assembly Checked------" & vbCrLf
	OutputText = OutputText & GetFileNameNoPathForDoc(oDoc, True) & vbCrLf
	OutputText = OutputText & "------Replaced Files-------" & vbCrLf
	OutputText = OutputText & ReplacedText & vbCrLf
	OutputText = OutputText & "------Ignored Files-------" & vbCrLf
	OutputText = OutputText & "Reason: No File Found" & vbCrLf
	OutputText = OutputText & IgnoredNoFileText & vbCrLf
	OutputText = OutputText & SubOutputText & vbCrLf

	Return OutputText
End Function



Public Function UpdatePartNamesAsm(oDoc As AssemblyDocument, oldText As String, newText As String) As String
	'''Creator: Chris Kuchman
	'''Date Made: 6/17/2020
	'''Date Updated: 
	'''Description: Takes in a assembly document and checks all subordinate parts and assemblies (and theirs) to find cases where the start
	'''of the part name should be updated. To recieve an update the following must be true for a part:
	'''1. The old part name starts with the old text string (will not update middle or right part name changes)
	'''2. The replaced new part name matches the file name of the part
	'''3. The part name exists in the same folder as the top level assembly
	'''Returns: A string log of the successful and failed updates
	
	'Generate text blocks for the final results
	IgnoredTextPN = ""
	IgnoredTextStartText = ""
	IgnoredTextPath = ""
	ChangedText = ""
	
	'Determine the documents path
	pathLength = InStrRev(oDoc.FullFileName, "\", -1)
	oDocPath = Left(oDoc.FullFileName, PathLength)

	'Get list of all subpart documents
	Dim refDocs As List(Of Document) = GetRefDocList(oDoc)
	
	'Add the top level to the list
	refDocs.Add(oDoc)

	'Go over each unique assembly or part in assembly
	For Each refDoc As Document In refDocs

		'Get the part name
		partName = refDoc.PropertySets.Item("Design Tracking Properties").Item("Part Number").Value
		
		'Get file name with and without extension
		FileName = GetFileNameNoPathForDoc(refDoc)
		
		'Get folder location of file
		pathLength = InStrRev(refDoc.FullFileName, "\", -1)
		refDocPath = Left(refDoc.FullFileName, PathLength)

		'Generate new part name to use
		newName = ReplaceFrontText(partName, oldText, newText)

		'Check if the part is in the same folder as the top level
		If Not oDocPath = refDocPath Then
			IgnoredTextPath = IgnoredTextPath & partName & vbCrLf
		
		'Check if the New Name could not be generated as it didn't find a valid new name
		ElseIf newName = "" Then
			IgnoredTextStartText = IgnoredTextStartText & "Old PN: " & partName & vbCrLf

		Else
			'Check if the Part Name and File Name do not match
			If Not newName = FileName Then
				IgnoredTextPN = IgnoredTextPN & "New PN: " & newName & vbTab & "FN: " & FileName & vbCrLf

			Else
				'Update the Part Number
				refDoc.PropertySets.Item("Design Tracking Properties").Item("Part Number").Value = NewName
				ChangedText = ChangedText & "Edited: " & partName & vbTab & vbTab & "Changed to: " & newName
				
				'Add warning for those that go over the 15 character frontier limit
				If Len(NewName) > 15 Then
					ChangedText = ChangedText & vbTab & "Warning: PN longer that 15 characters" & vbCrLf	
				Else
					ChangedText = ChangedText & vbCrLf
				End If
			End If
		End If
	Next
	
	'Generate output string log
	OutputText = OutputText & "------Changed Part Names-------" & vbCrLf
	OutputText = OutputText & ChangedText & vbCrLf
	OutputText = OutputText & "------Ignored Part Names-------" & vbCrLf
	OutputText = OutputText & "Reason: Start Text Doesn't Match Passed Value" & vbCrLf
	OutputText = OutputText & "Tried to Change " & oldText & " to " & newText & vbCrLf
	OutputText = OutputText & IgnoredTextStartText & vbCrLf
	OutputText = OutputText & "Reason: Changed Part Name Doesn't Match File Name" & vbCrLf
	OutputText = OutputText & IgnoredTextPN & vbCrLf
	OutputText = OutputText & "Reason: Not in same folder as top level" & vbCrLf
	OutputText = OutputText & IgnoredTextPath & vbCrLf

	Return OutputText
End Function


Public Function UpdateCodeAsm(oDoc As AssemblyDocument, oldText As String, newText As String) As String
	'''Creator: Chris Kuchman
	'''Date Made: 6/17/2020
	'''Date Updated: 
	'''Description: Takes in a assembly document and checks all subordinate parts and assemblies (and theirs) to find cases where the start
	'''of the part name should be updated in the code (all rules). To have code updated the following must be true:
	'''1. The code to edit takes the form "OldFileName" or "OldFileName:
	'''2. The file name that is being updated and the file that is having codde changed are both in the same fodler as the top level asm
	'''3. The old file name can be sucessfully reproduced by by just swapping the start of the filenames newText with the oldText
	'''Returns: A string log of the successful and failed updates
	
	'Generate text blocks for the final results
	IgnoredCodeStartText = ""
	IgnoredCodePath = ""
	ChangedCode = ""
	
	'Determine the documents path
	pathLength = InStrRev(oDoc.FullFileName, "\", -1)
	oDocPath = Left(oDoc.FullFileName, PathLength)

	'Get list of all subpart documents
	Dim refDocs As List(Of Document) = GetRefDocList(oDoc)
	
	'Add the top level to the list
	refDocs.Add(oDoc)	

	'Store all changed files
	Dim ChangedDocs As List(Of Document) = New List(Of Document)()
	
	'Go over each unique assembly or part in assembly to check for parts to change
	For Each refDoc As Document In refDocs

		'Get file name without extension
		FileName = GetFileNameNoPathForDoc(refDoc)
		
		'Get folder location of file
		pathLength = InStrRev(refDoc.FullFileName, "\", -1)
		refDocPath = Left(refDoc.FullFileName, PathLength)
		
		'Check if the part is not in the same folder as the top level part
		If Not oDocPath = refDocPath Then
			IgnoredCodePath = IgnoredCodePath & refDoc.FullFileName & vbCrLf

		'If the file does not match the new string start then ignore
		ElseIf Not FileName.StartsWith(newText) Then
			IgnoredCodeStartText = IgnoredCodeStartText & FileName & vbCrLf

		Else
			ChangedDocs.Add(refDoc)
		End If
	Next


	'Go over each unique assembly or part in assembly and update the code
	For Each refDoc As Document In refDocs

		'Get folder location of file
		pathLength = InStrRev(refDoc.FullFileName, "\", -1)
		refDocPath = Left(refDoc.FullFileName, PathLength)

		If Not oDocPath = refDocPath Then
			'Ignore if not in the top levels folder
		Else
			For Each ChangedDoc As Document In ChangedDocs

				'Get hypothetical old name
				NewFileName = GetFileNameNoPathForDoc(ChangedDoc)
				OldFileName = ReplaceFrontText(NewFileName, newText, oldText)
	
				result = ReplaceLogicPartNameAllRules(refDoc, NewFileName, OldFileName)
				
				If result <= 0 Then
					'No change made, text for debugging
					'ChangedCode = ChangedCode & "No Change--- " & "for " & OldFileName & " to " & NewFileName & " in " & refDoc.FullFileName & vbCrLf
				Else
					ChangedCode = ChangedCode & "Code Changed " & "for " & OldFileName & " to " & NewFileName & " in " & refDoc.FullFileName & vbCrLf
				End If
				
				'Reset Value
				result = 0
			Next
		End If
	Next
	
	'Generate output string log
	OutputText = OutputText & "------Changed Code-------" & vbCrLf
	OutputText = OutputText & ChangedCode & vbCrLf
	OutputText = OutputText & "------Ignored Code-------" & vbCrLf
	OutputText = OutputText & "Reason: Start Text Doesn't Match Current File Name" & vbCrLf
	OutputText = OutputText & "Tried to Change " & oldText & " to " & newText & vbCrLf
	OutputText = OutputText & IgnoredCodeStartText & vbCrLf
	OutputText = OutputText & "Reason: Not in same folder as top level" & vbCrLf
	OutputText = OutputText & IgnoredCodePath & vbCrLf

	Return OutputText
End Function


Public Function GetDocument(fullDocName As String) As Document
	'''Creator: Chris Kuchman
	'''Date Made: 6/9/2020
	'''Date Updated: 6/12/2020 - CAK
	'''Description: Gets the document of the same name as the passed in document name.
	'''If it fails to find it already loaded into Inventor (by being open or unsuppressed)
	'''it will try to open the file.
	'''WARNING: If the document was last opened in another project, inventor will automatically
	'''look for that one. The part must be opening in the correct project (through unsupressing it
	'''in a assembly it is in or ?????)
	
	Dim oDoc As Document
	
	Try
		'Try to access document, will fail if not visible (open or in open assembly unsuppressed)
		oDoc = ThisApplication.Documents.ItemByName(fullDocName)
	Catch
		Try
			'Try to open file to gain access, see WARNING
			oDoc = ThisApplication.Documents.Open(fullDocName)
		Catch
			MessageBox.Show("Failed to open " & fullDocName, "Function GetDocument")
		End Try
	End Try
	
	Return oDoc
End Function


Public Function GetDocumentFromOccurence(occ As ComponentOccurrence) As Document
	'''Creator: Chris Kuchman
	'''Date Made: 6/12/2020
	'''Date Updated: 
	'''Description: Gets the document of the same name as the passed in occurence by opening it in the background.
	
	Dim oDoc As Document
	
	Try
		'Check if the part is suppressed, if so then toggle it to 
		ActiveSuppressed = occ.Suppressed()
	
		If ActiveSuppressed = True Then
			occ.Unsuppress()
			occ.Suppress(True)
		End If
		
		'Try to open file to gain access
		oDoc = ThisApplication.Documents.Open(occ.ReferencedDocumentDescriptor.FullDocumentName, False)
	Catch
		MsgBox("Failed to open " & fullDocName, "Function GetDocumentFromOccurence")
	End Try
	
	Return oDoc
End Function


Public Function GetRefDocList(oDoc As AssemblyDocument) As List(Of Document)
	'''Creator: Chris Kuchman
	'''Date Made: 6/9/2020
	'''Date Updated: 6/12/2020 - CAK
	'''Description: Takes in a assembly document and returns a list of all unique assemblies
	'''and parts documents that are present, not including the passed in document.

	'Make list to store documents
	Dim refDocs As List(Of Document) = New List(Of Document)()

	'Check each occurence in specified document
	For Each occ As ComponentOccurrence In oDoc.ComponentDefinition.Occurrences
		Try

			'If the list doesn't have the document yet then add it
			If (refDocs.Contains(GetDocumentFromOccurence(occ)) = False) Then
				refDocs.Add(GetDocumentFromOccurence(occ))
			End If

			'If the occurence is a assembly then add all its occurences to the list to check
			If occ.DefinitionDocumentType = DocumentTypeEnum.kAssemblyDocumentObject Then
				Dim refDoc As Document = GetDocumentFromOccurence(occ)

				refDocs.AddRange(GetRefDocList(refDoc))
			End If
		Catch
			MessageBox.Show("Failed to get " & occ.ReferencedDocumentDescriptor.FullDocumentName, "Function GetRefDocList")
		End Try
	Next

	'Return list of unique occurences documents found
	Return refDocs
End Function


Public Function GetFileNameNoPathForDoc(oDoc As Document, Optional IncludeExt As Boolean = False) As String
	'''Creator: Chris Kuchman
	'''Date Made: 6/12/2020
	'''Date Updated: 
	'''Description: Returns just the file name for the document without the full file path. Optional boolean
	'''can be passed to include the extension which is off by default.
	
	Try
		'Get file name with path
		FilePathName = oDoc.FullFileName
		
		'Determine the position of the first folder indicator
		PathLength = InStrRev(FilePathName, "\", -1)
		
		'Remove file path
		FileName = Right(FilePathName, Len(FilePathName) - PathLength)
		
		'Remove Extension
		If Not IncludeExt Then
			FileName = Left(FileName, Len(FileName) - 4)
		End If
	Catch
		MessageBox.Show("Failed to get file name", "Function GetFileNameNoPathForDoc")
	End Try

	Return FileName
End Function


Public Function GetLogicText(oDoc As Document, ruleName As String) As String
	'''Creator: Chris Kuchman
	'''Date Made: 6/9/2020
	'''Date Updated: 6/12/2020 - CAK
	'''Description: Returns a string of the rule code matching the name specified in the document passed in. If the rule name does not match
	'''any rules in the document then it returns a blank string.
	
	'Checks for the iLogic Addin and the Autommaton variable
	Try
		iLogicAddin = ThisApplication.ApplicationAddIns.ItemById("{3bdd8d79-2179-4b11-8a5a-257b1c0263ac}")
		iLogicAutomation = iLogicAddin.Automation
	Catch ex As Exception
		MessageBox.Show("Unable to set variable iLogicAutomation or iLogic Add-in Missing.", "Function GetLogicText")
		Return ""
	End Try
	
	'Try to open the rule to read the text
	Try
		LogicText = iLogicAutomation.GetRule(oDoc, ruleName).Text
	Catch
		'Skip if fails to find the rule
	End Try
	
	Return LogicText
End Function


Public Function SetLogicText(oDoc As Document, ruleName As String, newText As String) As Integer
	'''Creator: Chris Kuchman
	'''Date Made: 6/9/2020
	'''Date Updated: 6/12/2020 - CAK
	'''Description: Sets the code of the specified drawings rule to the passed in string. A archive of the previous rule text will be archived onto 
	'''the users computer if a change has occured in case of error. 
	'''Returns:
	'''1: Part Changed
	'''0: No Change Found
	'''-1: No Rule Found
	'''-2: No iLogic Module Found
	
	
	'Checks for the iLogic Addin and the Autommaton variable
	Try
		iLogicAddin = ThisApplication.ApplicationAddIns.ItemById("{3bdd8d79-2179-4b11-8a5a-257b1c0263ac}")
		iLogicAutomation = iLogicAddin.Automation
	Catch ex As Exception
		Return -2
	End Try
	
	Try
		'Checks the rules of the document for the specified one
		For Each rule In iLogicAutomation.Rules(oDoc)
			If rule.Name = ruleName Then
				
				'Check to see if the rule has changed at all
				Change = String.Compare(GetLogicText(oDoc, ruleName), newText)
				
				If Change <> 0 Then
				
					'Archives the older code 
					'Check if folder exists else make it
					If System.IO.Directory.Exists("C:\temp\codeChanges") = False Then
						System.IO.Directory.CreateDirectory("C:\temp\codeChanges")
					End If
					
					FileName = GetFileNameNoPathForDoc(oDoc)
					
					'Format the date to make work as file name
					dateText = Now
					dateText = Replace(dateText, "/", "-")
					dateText = Replace(dateText, ":", "-")
	
					'Make a archive text file and store the old rule
					oldRuleArchive = GenerateTextFile(FileName & "-" & ruleName & "-" & dateText, "C:\temp\codeChanges\")
					WriteText(oldRuleArchive, rule.Text)
					
					'Updates the rule to the next code
					rule.Text = newText
				
					'Pass back a successful change
					Change = 1
				End If
				
				Return Change
			End If
		Next
	Catch
		'No rules exist
	End Try
	
	Return -1

End Function


Public Function ReplaceLogicPartNameAllRules(oDoc As Document, newText As String, oldText As String)
	'''Creator: Chris Kuchman
	'''Date Made: 6/9/2020
	'''Date Updated: 6/12/2020 - CAK
	'''Description: Replaces the instances of the old text in all of the specified document's rules only in 
	'''the forms "oldtext" or "oldtext: to reduce chance of changing non file name strings and hitting variables
	'''Returns the lowest case of the following between the two types:
	'''1: Part Changed
	'''0: No Change Found
	'''-1: No Rule Found
	'''-2: No iLogic Module Found

	Result1 = ReplaceLogicTextAllRules(oDoc, """" & newText & """", """" & oldText & """")
	Result2 = ReplaceLogicTextAllRules(oDoc, """" & newText & ":", """" & oldText & ":")
	
	'If one fails for missing rule or module then both with
	Return Max(Result1, Result2)
End Function


Public Function ReplaceLogicTextAllRules(oDoc As Document, newText As String, oldText As String) As Integer
	'''Creator: Chris Kuchman
	'''Date Made: 6/9/2020
	'''Date Updated: 6/12/2020 - CAK
	'''Description: Replaces the instances of the old text in all of the specified document's rules with the new string.
	'''Returns:
	'''1: Part Changed
	'''0: No Change Found
	'''-1: No Rule Found
	'''-2: No iLogic Module Found
	
	'Checks for the iLogic Addin and the Autommaton variable
	Try
		iLogicAddin = ThisApplication.ApplicationAddIns.ItemById("{3bdd8d79-2179-4b11-8a5a-257b1c0263ac}")
		iLogicAutomation = iLogicAddin.Automation
	Catch ex As Exception
		MessageBox.Show("Unable to set variable iLogicAutomation or iLogic Add-in Missing.", "Function ReplaceLogicTextAllRules")
		Return -2
	End Try
	
	Try
		'Try to modify each rule
		For Each rule In iLogicAutomation.Rules(oDoc)

			RuleChangeResult = ReplaceLogicTextRule(oDoc, newText, oldText, rule.Name)
			
			If RuleChangeResult > ChangeResult Then
				ChangeResult = RuleChangeResult
			End If
		Next
	Catch
		'No rules found
		ChangeResult = -1
	End Try
	
	Return ChangeResult
End Function


Public Function ReplaceLogicTextRule(oDoc As Document, newText As String, oldText As String, ruleName As String) As Integer
	'''Creator: Chris Kuchman
	'''Date Made: 6/9/2020
	'''Date Updated: 6/12/2020 - CAK
	'''Description: Replaces the instances of the old text in the specified document's specified rule with the new string.
	'''Returns:
	'''1: Part Changed
	'''0: No Change Found
	'''-1: No Rule Found
	'''-2: No iLogic Module Found

	'Gets code string
	oldCode = GetLogicText(oDoc, ruleName)

	'Replaces the text in the string
	newCode = Replace(oldCode, oldText, newText)

	'Sets the code of the rule to the new text
	Outcome = SetLogicText(oDoc, ruleName, newCode)
	
	Return Outcome
End Function


Public Function ReplaceFrontText(text As String, oldSection As String, newSection As String) As String
	'''Creator: Chris Kuchman
	'''Date Made: 6/9/2020
	'''Date Updated: 
	'''Description: Replaces the front text of a string with a new set of text, if the front text does not
	'''match the specified old substring then a blank string is passed back.
	
	If Left(text, Len(oldSection)) = oldSection Then
		result = newSection & Right(text, Len(text) - Len(oldSection))
	Else
		result = ""
	End If

	Return result
End Function


Public Function GenerateTextFile(fileName, Optional fileLocation = "C:\temp\") As String
	'''Creator: Chris Kuchman
	'''Date Made: 6/9/2020
	'''Date Updated: 
	'''Description: Generates a text file of the passed in name, in the file location specified.
	'''If the file already exists then the text file is cleared out

	'Specifies file name to be written to
	textFile = fileLocation & fileName & ".txt"

	'Creates & Clears out a text file
	System.IO.File.WriteAllText(fileLocation & fileName & ".txt",String.Empty)
	
	Return textFile
End Function


Public Function OpenTextFile(fileName)
	'''Creator: Chris Kuchman
	'''Date Made: 6/9/2020
	'''Date Updated: 
	'''Description: Opens up the text file to the screen, if it does not exist then a msgbox will pop up instead	
	
	'Check if the file exists
	If System.IO.File.Exists(fileName) = True Then
		'Open the file
		Process.Start(fileName)
	Else
		MessageBox.Show("Error in opening file " & fileName)
	End If
End Function


Public Function WriteText(File, Text, Optional EndWithNewLines = 2)
	'''Creator: Chris Kuchman
	'''Date Made: 1/27/2016
	'''Date Updated: 2/6/2016 - CAK
	'''Description: Used to write text to a text file. The first arguement is the specific text file you
	'''are writing to and the second is the string you want to pass. If you want the string to be broken up into seperate
	'''lines then add a \n to the string line. By default the string will add 2 new lines between each new string added,
	'''but if you want to add less or more new lines then pass a third argument with the number of new lines generated.
	'''(0 will just append the line to the last line)

	'Sets a stream to pass the text into the notepad file (filestreams only do btyes so we need a stream writer to convert)
	Dim fs As New System.IO.FileStream(File, System.IO.FileMode.Append, System.IO.FileAccess.Write)
	Dim theLog As New System.IO.StreamWriter(fs)
	
	'Breaks the string up into new lines
	Dim StringArray() As String = Split(Text, "\n ")
	
	'For each split string, write to the file and add a new line (except for the very last line)
	For i As Integer = 0 To StringArray.Length - 1
		If i < StringArray.Length - 1  Then
			theLog.WriteLine(StringArray(i))
		Else
			theLog.Write(StringArray(i)) 'Write will not add a new line by default like WriteLine
		End If
	Next
	
	Dim j As Integer = 0
	
	'Add the number of new lines passed into the optional parameter, will loop once if the default value is used
	While EndWithNewLines > j
		theLog.WriteLine()
		j += 1
	End While
	​
	'Closes the stream
	theLog.Close()
End Function
