'''Creator: 		Douglas Wisser
'''Creation Date:	07.19.2017
'''Revision:		0
'''Revision Date:	0
'''Inputs:			Interior Finish (INFIN)
'''Outputs:			Hardware Finish (GROMFIN) and Errors (ERRORS)
'''Description:		This function is indended for use with any Mercury storage that utilizes the tonic grommets.
'''					This includes the HD4H And a Number Of Hub And storage studios. Its purpose is to drive the
'''					correct color grommet for a given interior finish. If the supplied finish has not yet been entered,
'''					the rule will output an error into the Process rule.  In this case, a GROMFIN of 'FQ'
'''					corresponds to a grey grommet and a GROMFIN of 'BK' corresponds to a charcoal grommet.




FileName = ThisDoc.FileName(True)								'with extension

Dim ERRORS As String = ""										'Initialize ERRORS Text
Dim GROMFIN As String = ""										'Initialize GROMFIN Text
Dim INFIN As String = iProperties.Value("Custom", "INFIN")		'Pull in Interior Finish from model

Select Case INFIN

Case "BK"					'Black
	GROMFIN = "CH"
Case "CH"					'Charcoal
	GROMFIN = "CH"
Case "FJ"					'Frosty White
	GROMFIN = "FQ"
Case "FQ"					'Fashion Grey
	GROMFIN = "FQ"
Case "GY"					'Satin Grey
	GROMFIN = "CH"
Case "M2"					'Dark Champagne
	GROMFIN = "FQ"
Case "SG"					'Slate
	GROMFIN = "CH"
Case "TBD"					'TBD FOR TESTING
	GROMFIN = "FQ"
Case "WA"					'FQ (White Aluminum)
	GROMFIN = "FQ"
Case Else
	ERRORS = ERRORS & "ERROR IN MERCURYHUB-GROMMETCOLOR-CALCULATOR RULE. SELECTED INFIN IS NOT IN THE MATRIX. PLEASE LOAD INFIN AND PUBLISH RULE. " & FileName & " /n"
End Select

iProperties.Value("Custom", "ERRORS") = iProperties.Value("Custom", "ERRORS") & ERRORS
iProperties.Value("Custom", "GROMFIN") = GROMFIN
