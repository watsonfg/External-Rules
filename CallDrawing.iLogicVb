'['Declare External Routine(s)
AddVbFile "classDrawingExport.v2.vb" 'Defines external rule
AddVbFile "DebugHelper.vb" 'Defines external rule
Dim drawing As New DrawingExportV2(ThisDoc.Document, ThisApplication)
Dim Dbg as New DebugHelper(ThisDoc.Document, SharedVariable)
Try : 'Dbg.DumpProperties() : 'Dbg.DumpParameters()
']

'['Toggle all message boxes: 3 Types 
'1st: toggles all saved message boxes to show values, in this iam
ShowValueMsg = False

'2nd: toggles "OK" message boxes in 2 specific external rules, Helpful to troubleshoot Parts or Assemblies
SharedVariable("ShowOkMsgWoodPart") = False
SharedVariable("ShowOkMsgWoodAsm") = False

'3rd: toggles all Error and Warning message boxes in this iam, Uses Environment Variable from Computer running Inventor
'Set to "true" for development PC and "false" for Server running Frontier cadflow.
'Ensures Auto Off for all MsgBoxes when model Is published
Dim ErrMsg As String = Environ("ILOGIC_ErrMsg")
If ErrMsg = "true" Then 
	ShowErrWarnMsg = True
Else		'If the PC is missing the Environment Variable then ShowErrWarnMsg will be set to false 
	ShowErrWarnMsg = False
	'Safety rules, override any true back to false in case on server
	ShowValueMsg = False	
	SharedVariable("ShowOkMsgWoodPart") = False
	SharedVariable("ShowOkMsgWoodAsm") = False
End If
']



Dbg.Log("CreateDrawingV2 Called: " & ThisDoc.Document.FullFileName)

' in development the log will write to = "c:\temp\ilogic.log"
Call drawing.CreateDrawing()

Dbg.Log("CreateDrawingV2 Completed: " & ThisDoc.Document.FullFileName)



'['Send any caught exceptions to ERRORS and log and Development user
ERRORS = iProperties.Value("Custom", "ERRORS") 'must update ERRORS variable, values could come from external rule
Catch ex As Exception
	ExFull = ("Fatal error in model … " & ThisDoc.PathAndFileName(False) & "\n  Msg: " & ex.Message & "\n   More Info: " & ex.ToString)
	ExBrief = ("Fatal error in model …" & ThisDoc.FileName(True) & "\n  Msg: " & ex.Message)
	ERRORS = ERRORS & Left(ExBrief,255)
	iProperties.Value("Custom", "ERRORS") = ERRORS
	Dbg.Log("1of1 Catch from Call to CreateDrawingV2: " & ExFull)
	'Shows full text description as message box durring development	
	If ShowErrWarnMsg Then	MessageBox.Show(ExFull, "Development Only 'More Info' Message.  From: "& ThisDoc.FileName(True))
End Try

If ShowErrWarnMsg Then If ERRORS <> "" Then MessageBox.Show(ERRORS, "ERRORS from: "& ThisDoc.FileName(True))

']
